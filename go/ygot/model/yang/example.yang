module network {
  prefix "net";
  namespace "urn:network";
  // meta
  organization "Actus Networks";

  contact 
      "neoul@ymail.com";

  // Max line length throughout the modules should be 70 cols.

  // Formatting description statements: for consistency, the
  // description text should start on the line following the
  // 'description' keyword and be indented 2 spaces.
  description
    "example model description!";

  revision "2020-06-01" {
    description
      "Inital model";
    reference "0.1.1";
  }

  leaf person { type string; }

  leaf married { type empty; }

  list country {
    key "name";

    leaf name { type string; }
    leaf country-code { type string; }
    leaf dial-code { type uint32 { range "1..492"; } }
  }

  list operator {
    key "asn";
    leaf asn { type uint32; }
    leaf name { type string; }
  }

  list multikeylist {
    key "str integer";
    leaf integer { type uint32; }
    leaf str { type string; }
  }

  container company {
    leaf-list address {
      type string;
    }
    leaf name {
      type string;
    }
    leaf enumval {
      type enumeration {
         enum enum1;
         enum enum2;
         enum enum3 {
           value 30;
         }
      }
    }
  }
}
