module sample {
  prefix "net";
  namespace "urn:network";
  // meta
  organization "sample model";

  contact "neoul@ymail.com";

  // Max line length throughout the modules should be 70 cols.

  // Formatting description statements: for consistency, the
  // description text should start on the line following the
  // 'description' keyword and be indented 2 spaces.
  description
    "example model description!";

  revision "2020-06-01" {
    description
      "Inital model";
    reference "0.1.1";
  }

  typedef enumtypedef {
    type enumeration {
      enum e1;
      enum e2;
      enum e3 {
        value 100;
      }
    }
  }

  container sample {
    leaf str-val { type string; }
    leaf empty-val { type empty; }
    list single-key-list {
      key "list-key";
      leaf list-key { type string; }
      leaf country-code { type string; }
      leaf dial-code { type uint32 { range "1..492"; } }
    }

    list multiple-key-list {
      key "str integer";
      leaf integer { type uint32; }
      leaf str { type string; }
      leaf ok {type boolean;}
    }

    container container-val {
      leaf-list leaf-list-val {
        type string;
      }
      
      leaf-list leaf-list-v2 {
        type int32;
      }

      leaf enum-val {
        type enumeration {
          enum enum1;
          enum enum2;
          enum enum3 {
            value 30;
          }
        }
      }
      leaf union-value {
        type union {
          type uint16;
          type string;
          type enumtypedef;
        }
      }
    }
  }
  
}
